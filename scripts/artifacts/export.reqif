# Specification: Extractor Requirements

## doc-sample:1
- The system shall operate between -40C and +85C.
- {"section_id": "sec-1", "breadcrumb": ["1", "Introduction"], "evidence": {"page": 1}, "lean4_status": "unknown"}
